import FreeCAD
import FreeCADGui
import numpy as np  
import Part
import Draft
import random

def DFS(all_point, z_values_minimum, z_values, i, color):
    all_point[i] = color
    z_values_minimum[i] = 1000

    for j in points_connection[i]:
            if (all_point[j] != 0):
                continue
            if (z_values[i] <= z_values[j]):
                all_point, z_values_minimum, z_values, color = DFS(all_point, z_values_minimum, z_values, j, color)

    return all_point, z_values_minimum, z_values, color

def find_peaks(mesh, points_connection):
    all_point = np.full(len(mesh.Mesh.Topology[0]), 0)

    z_values_minimum = np.array(mesh.Mesh.Topology[0])[:, 1]
    z_values = np.array(mesh.Mesh.Topology[0])[:, 1]
    color = 1

    while z_values_minimum[np.argmin(z_values_minimum)] < 900:
        main_point = np.argmin(z_values_minimum)
        
        all_point[main_point] = color
        z_values_minimum[main_point] = 1000

        for j in points_connection[main_point]:
            if (all_point[j] != 0):
                continue
            if (z_values[main_point] <= z_values[j]):
                all_point, z_values_minimum, z_values, color = DFS(all_point, z_values_minimum, z_values, j, color)
        color += 1
    return all_point, color

mesh_obj = FreeCAD.ActiveDocument.getObject('isosurface002')

points_connection = []
for i in mesh_obj.Mesh.Topology[0]:
    points_connection.append(set())

for a, b, c in mesh_obj.Mesh.getFaces(1)[1]:
    points_connection[a].add(b)
    points_connection[a].add(c)
    points_connection[b].add(a)
    points_connection[b].add(c)
    points_connection[c].add(a)
    points_connection[c].add(b)

peaks, color = find_peaks(mesh_obj, points_connection)
print(peaks)
for i in range(1, color):
    arr = np.array(mesh_obj.Mesh.Topology[0])[np.where(peaks == i)[0]]
    vert = []
    for a, b, c in arr:
        vert.append(FreeCAD.Vector(a, b, c))

    wire = Part.makePolygon(vert)
    plane = Part.Plane(vert[0], vert[1], vert[2])
    face=Part.Face(plane, wire)
    shape = Part.Shape(face)
    docObj = App.ActiveDocument.addObject("Part::Feature","Box")
    docObj.Shape = shape
    r = random.randint(0, 255)
    g = random.randint(0, 255)
    b = random.randint(0, 255)
    docObj.ViewObject.ShapeColor = (r/255, g/255, b/255)

FreeCAD.ActiveDocument.recompute()
